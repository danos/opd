module vyatta-system-acm-opd-v1 {
	namespace "urn:vyatta.com:mgmt:vyatta-system-acm-opd:1";
	prefix vyatta-system-acm-opd-v1;

	import vyatta-system-v1 {
		prefix system;
	}
	import vyatta-system-acm-v1 {
		prefix system-acm;
	}
	import configd-v1 {
		prefix configd;
	}

	organization "AT&T Inc.";
	contact
		"AT&T
		 Postal: 208 S. Akard Street
				 Dallas, TX 75202
		 Web: www.att.com";

	description
		"Copyright (c) 2018-2019 AT&T Intellectual Property
		 All rights reserved.

		 Copyright (c) 2014-2016 by Brocade Communications Systems, Inc.
		 All rights reserved.

		 Redistribution and use in source and binary forms, with or without
		 modification, are permitted provided that the following conditions
		 are met:

		 1. Redistributions of source code must retain the above copyright
		    notice, this list of conditions and the following disclaimer.
		 2. Redistributions in binary form must reproduce the above
		    copyright notice, this list of conditions and the following
		    disclaimer in the documentation and/or other materials provided
		    with the distribution.
		 3. Neither the name of the copyright holder nor the names of its
		    contributors may be used to endorse or promote products derived
		    from this software without specific prior written permission.

		 THIS SOFTWARE IS PROVIDED BY THE COPYRIGHT HOLDERS AND CONTRIBUTORS
		 'AS IS' AND ANY EXPRESS OR IMPLIED WARRANTIES, INCLUDING, BUT NOT
		 LIMITED TO, THE IMPLIED WARRANTIES OF MERCHANTABILITY AND FITNESS
		 FOR A PARTICULAR PURPOSE ARE DISCLAIMED. IN NO EVENT SHALL THE
		 COPYRIGHT HOLDER OR CONTRIBUTORS BE LIABLE FOR ANY DIRECT, INDIRECT,
		 INCIDENTAL, SPECIAL, EXEMPLARY, OR CONSEQUENTIAL DAMAGES (INCLUDING,
		 BUT NOT LIMITED TO, PROCUREMENT OF SUBSTITUTE GOODS OR SERVICES;
		 LOSS OF USE, DATA, OR PROFITS; OR BUSINESS INTERRUPTION) HOWEVER
		 CAUSED AND ON ANY THEORY OF LIABILITY, WHETHER IN CONTRACT, STRICT
		 LIABILITY, OR TORT (INCLUDING NEGLIGENCE OR OTHERWISE) ARISING IN
		 ANY WAY OUT OF THE USE OF THIS SOFTWARE, EVEN IF ADVISED OF THE
		 POSSIBILITY OF SUCH DAMAGE.

		 SPDX-License-Identifier: BSD-3-Clause

		 The YANG module for opd's access control mechanism";

	revision 2018-07-02 {
		description "Rework operational-ruleset validation to use YANG
		             validation";
	}
	revision 2016-03-25 {
		description "Add execution of operational rule-set update";
	}
	revision 2015-08-14 {
		description "Initial revision of version 1.";
	}

	augment /system:system/system-acm:acm {
		configd:end "vyatta-update-opruleset.pl";
		leaf exec-default {
			type enumeration {
				enum "allow" {
					configd:help "Allow the action";
				}
				enum "deny" {
					configd:help "Deny the action";
				}
			}
			default "allow";
			configd:help "Execute operation default action";
			configd:allowed "/opt/vyatta/share/tmplscripts/system/acm/exec-default/configd_allowed.sh";
		}
		container operational-ruleset {
			presence "true";
			configd:help "Operational command ruleset";
			list rule {
				configd:help "Rule number (1-9999)";
				key "tagnode";
				leaf tagnode {
					type uint32 {
						range 1..9999 {
							error-message "Rule number must be between 1 and 9999";
						}
					}
					configd:help "Rule number (1-9999)";
				}
				leaf action {
					type enumeration {
						enum "allow" {
							configd:help "Allow the action";
						}
						enum "deny" {
							configd:help "Deny the action";
						}
					}
					default "deny";
					configd:help "Action";
					configd:allowed "/opt/vyatta/share/tmplscripts/system/acm/operational-ruleset/rule/action/configd_allowed.sh";
				}
				leaf command {
					type string;
					mandatory "true";
					configd:help "Path to match";
				}
				leaf-list group {
					type string;
					ordered-by "user";
					configd:help "Group to match";
					configd:allowed "/opt/vyatta/share/tmplscripts/system/acm/operational-ruleset/rule/group/configd_allowed.sh";
				}
				leaf log {
					type empty;
					configd:help "Enable logging for rule";
				}
			}
		}
	}
}
